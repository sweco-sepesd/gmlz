FME workspace read_using_index.fmw

Parameters:
- SourceDataset_SQLITE3 = C:\Users\sepesd\Downloads\167_CadastralParcel.db   # SQLite Database
- SRC_GML = C:\Users\sepesd\Downloads\167_CadastralParcel.gml   # Source GML File

Readers:
- SQLITE3_1: SQLITE3 from $(SourceDataset_SQLITE3)

gml_id (reader SQLITE3_1)
    attributes: pos integer, gml_id text
    -> AttributeCreator
AttributeCreator
    ATTR_TABLE = SET_TO _gml_src_file = $(SRC_GML)
    -> PythonCaller
PythonCaller
    NEW_ATTRIBUTES = _gml_content
    PYTHONSYMBOL = FeatureProcessor
    PYTHONSOURCE:
      class FeatureProcessor(object):
          def __init__(self):
              self.fin = None
          def input(self,feature):
              if not self.fin:
                  self.fin = open(feature.getAttribute('_gml_src_file'), 'r')
              pos = feature.getAttribute('pos')
              self.fin.seek(pos)
              feature.setAttribute('_gml_content', self.fin.read(100))
              self.pyoutput(feature)
          def close(self):
              if(self.fin):
                  self.fin.close()
    -> PythonCaller_Output
PythonCaller_Output: Logger
    MAXCOORDS = 20
    MESSAGE = Feature is:
    MAXFEATS = 20
